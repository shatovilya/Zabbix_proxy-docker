RADLAN-iscsi-MIB DEFINITIONS ::= BEGIN

-- Title:      RADLAN iSCSI snooping Configuration
-- Version:    7.45.00.00
-- Date:       24-June-2007
--

IMPORTS
    TruthValue, TEXTUAL-CONVENTION, TimeStamp,
    DisplayString, DateAndTime, RowStatus                FROM SNMPv2-TC
    TimeTicks, IpAddress, NOTIFICATION-TYPE,
    MODULE-IDENTITY, OBJECT-TYPE, Unsigned32             FROM SNMPv2-SMI
    rnd                                                  FROM RADLAN-MIB;



rlIscsiSnoop  OBJECT IDENTIFIER ::= { rnd 126 }

-------------------------------------------------------------------------------
rlIscsiSnoopEnable OBJECT-TYPE
    SYNTAX      TruthValue
    MAX-ACCESS  read-write
    STATUS      current
    DESCRIPTION
        "Enable/Disable iSCSI Snooping in the switch."
    ::= { rlIscsiSnoop 1 }


-------------------------------------------------------------------------------
rlIscsiSnoopAgingTimeOut OBJECT-TYPE
    SYNTAX      INTEGER (60..2592000)
    MAX-ACCESS  read-write
    STATUS      current
    DESCRIPTION
        "The time in seconds that should pass before session aging out
         after the last frame transmitted for the session."
    ::= { rlIscsiSnoop 2 }


-------------------------------------------------------------------------------
QosType ::= TEXTUAL-CONVENTION
    STATUS current
    DESCRIPTION
        "Type of QoS: VPT or DSCP."
    SYNTAX  INTEGER {
        vpt(0),
        dscp(1)
}


rlIscsiSnoopQosTable OBJECT-TYPE
   SYNTAX  SEQUENCE OF RlIscsiSnoopQosEntry
    MAX-ACCESS   not-accessible
    STATUS   current
    DESCRIPTION
       "The (conceptual) table for configuration of iSCSI QOS."
    ::= {  rlIscsiSnoop 3 }

rlIscsiSnoopQosEntry OBJECT-TYPE
    SYNTAX      RlIscsiSnoopQosEntry
    MAX-ACCESS  not-accessible
    STATUS      current
    DESCRIPTION
        "An entry (conceptual row) in the rlIscsiSnoopQosTable."
    INDEX  { rlIscsiSnoopQosKey }
    ::= { rlIscsiSnoopQosTable 1 }

RlIscsiSnoopQosEntry::= SEQUENCE {
   rlIscsiSnoopQosKey                                    INTEGER,
   rlIscsiSnoopQosType                                  QosType,
   rlIscsiSnoopQosValue                                 INTEGER,
   rlIscsiSnoopQosRemark                             TruthValue
}

rlIscsiSnoopQosKey OBJECT-TYPE
    SYNTAX      INTEGER (1)
    MAX-ACCESS  not-accessible
    STATUS      current
    DESCRIPTION
        "Key of the rlIscsiSnoopQosTable table"
    ::= { rlIscsiSnoopQosEntry 1 }

rlIscsiSnoopQosType OBJECT-TYPE
    SYNTAX      QosType
    MAX-ACCESS  read-write
    STATUS      current
    DESCRIPTION
        "Current type of QoS of iSCSI packets"
    ::= { rlIscsiSnoopQosEntry 2 }

rlIscsiSnoopQosValue OBJECT-TYPE
    SYNTAX      INTEGER (0..63)
    MAX-ACCESS  read-write
    STATUS      current
    DESCRIPTION
        "The value of VPT or DSCP, depends on rlIscsiSnoopQosType, that will be assigned to each iSCSI packet.
        The range of VPT value is 0..7. The range of DSCP value is 0..63"
    ::= { rlIscsiSnoopQosEntry 4 }

rlIscsiSnoopQosRemark OBJECT-TYPE
    SYNTAX      TruthValue
    MAX-ACCESS  read-write
    STATUS      current
    DESCRIPTION
        "Whether iSCSI frames with the configured VPT/DSCP when egressing the switch."
    ::= { rlIscsiSnoopQosEntry 5 }


-------------------------------------------------------------------------------
rlIscsiSnoopTargetConfigTable OBJECT-TYPE
   SYNTAX  SEQUENCE OF RlIscsiSnoopTargetConfigEntry
    MAX-ACCESS   not-accessible
    STATUS   current
    DESCRIPTION
       "The (conceptual) table for configuration of iSCSI target TCP port number
        IP address and name."
    ::= {  rlIscsiSnoop 4 }

rlIscsiSnoopTargetConfigEntry OBJECT-TYPE
    SYNTAX      RlIscsiSnoopTargetConfigEntry
    MAX-ACCESS  not-accessible
    STATUS      current
    DESCRIPTION
        "An entry (conceptual row) in the rlIscsiSnoopTargetPortConfigTable."
    INDEX  { rlIscsiSnoopTargetConfigTcpPort,
             rlIscsiSnoopTargetConfigAddr}
    ::= { rlIscsiSnoopTargetConfigTable 1 }

RlIscsiSnoopTargetConfigEntry::= SEQUENCE {
   rlIscsiSnoopTargetConfigTcpPort                INTEGER,
   rlIscsiSnoopTargetConfigAddr                   IpAddress,
   rlIscsiSnoopTargetConfigName1                  DisplayString(SIZE(0..160)),
   rlIscsiSnoopTargetConfigName2                  DisplayString(SIZE(0..63)),
   rlIscsiSnoopTargetConfigStatus                 RowStatus
}

rlIscsiSnoopTargetConfigTcpPort OBJECT-TYPE
    SYNTAX      INTEGER
    MAX-ACCESS  not-accessible
    STATUS      current
    DESCRIPTION
        "The TCP port of configured target."
    ::= { rlIscsiSnoopTargetConfigEntry 1 }

 rlIscsiSnoopTargetConfigAddr OBJECT-TYPE
    SYNTAX      IpAddress
    MAX-ACCESS  not-accessible
    STATUS      current
    DESCRIPTION
        "Specifies the target address. If the target
        address is ignored the address should be 0.0.0.0"
    ::= { rlIscsiSnoopTargetConfigEntry 3 }

rlIscsiSnoopTargetConfigName1 OBJECT-TYPE
    SYNTAX  DisplayString(SIZE(0..160))
    MAX-ACCESS  read-write
    STATUS  current
    DESCRIPTION
        "The first part of target name"
    DEFVAL {""}
    ::=  { rlIscsiSnoopTargetConfigEntry 4 }

rlIscsiSnoopTargetConfigName2 OBJECT-TYPE
    SYNTAX  DisplayString(SIZE(0..63))
    MAX-ACCESS  read-write
    STATUS  current
    DESCRIPTION
        "The second part of target name"
    DEFVAL {""}
    ::=  { rlIscsiSnoopTargetConfigEntry 5 }

rlIscsiSnoopTargetConfigStatus OBJECT-TYPE
    SYNTAX      RowStatus
    MAX-ACCESS  read-create
    STATUS      current
    DESCRIPTION
        "The status of the target. It's used to add/delete a target"
    ::= { rlIscsiSnoopTargetConfigEntry  6}


-------------------------------------------------------------------------------
rlIscsiSnoopTargetNameTable OBJECT-TYPE
    SYNTAX      SEQUENCE OF RlIscsiSnoopTargetNameEntry
    MAX-ACCESS  not-accessible
    STATUS      current
    DESCRIPTION
       "A table that contains iSCSI target names.
        It is indexed by Target Name ID."
    ::= { rlIscsiSnoop 5 }

rlIscsiSnoopTargetNameEntry OBJECT-TYPE
    SYNTAX      RlIscsiSnoopTargetNameEntry
    MAX-ACCESS  not-accessible
    STATUS      current
    DESCRIPTION
        "An entry (conceptual row) in the rlIscsiSnoopTargetNameTable."
    INDEX  { rlIscsiSnoopTargetNameId }
    ::= { rlIscsiSnoopTargetNameTable 1 }

RlIscsiSnoopTargetNameEntry ::= SEQUENCE {
    rlIscsiSnoopTargetNameId                    INTEGER,
    rlIscsiSnoopTargetName1                     DisplayString(SIZE(0..160)),
    rlIscsiSnoopTargetName2                     DisplayString(SIZE(0..63))
}

rlIscsiSnoopTargetNameId OBJECT-TYPE
    SYNTAX      INTEGER
    MAX-ACCESS  not-accessible
    STATUS      current
    DESCRIPTION
        "Numerical ID of target name assigned by system. "
    ::= { rlIscsiSnoopTargetNameEntry 1 }

rlIscsiSnoopTargetName1 OBJECT-TYPE
    SYNTAX  DisplayString(SIZE(0..160))
    MAX-ACCESS  read-only
    STATUS  current
    DESCRIPTION
        "The first part of target name"
    ::=  { rlIscsiSnoopTargetNameEntry 2 }

rlIscsiSnoopTargetName2 OBJECT-TYPE
    SYNTAX  DisplayString(SIZE(0..63))
    MAX-ACCESS  read-only
    STATUS  current
    DESCRIPTION
        "The second part of target name"
    ::=  { rlIscsiSnoopTargetNameEntry 3 }



-------------------------------------------------------------------------------
rlIscsiSnoopInitiatorNameTable OBJECT-TYPE
    SYNTAX      SEQUENCE OF RlIscsiSnoopInitiatorNameEntry
    MAX-ACCESS  not-accessible
    STATUS      current
    DESCRIPTION
       "A table that contains iSCSI initiator names.
        It is indexed by Target Name ID."
    ::= { rlIscsiSnoop 6 }

rlIscsiSnoopInitiatorNameEntry OBJECT-TYPE
    SYNTAX      RlIscsiSnoopInitiatorNameEntry
    MAX-ACCESS  not-accessible
    STATUS      current
    DESCRIPTION
        "An entry (conceptual row) in the rlIscsiSnoopInitiatorNameTable."
    INDEX  { rlIscsiSnoopInitiatorNameId }
    ::= { rlIscsiSnoopInitiatorNameTable 1 }

RlIscsiSnoopInitiatorNameEntry ::= SEQUENCE {
    rlIscsiSnoopInitiatorNameId                    INTEGER,
    rlIscsiSnoopInitiatorName1                     DisplayString(SIZE(0..160)),
    rlIscsiSnoopInitiatorName2                     DisplayString(SIZE(0..63))
}

rlIscsiSnoopInitiatorNameId OBJECT-TYPE
    SYNTAX      INTEGER
    MAX-ACCESS  not-accessible
    STATUS      current
    DESCRIPTION
        "Numerical ID of initiator name assigned by system. "
    ::= { rlIscsiSnoopInitiatorNameEntry 1 }

rlIscsiSnoopInitiatorName1 OBJECT-TYPE
    SYNTAX  DisplayString(SIZE(0..160))
    MAX-ACCESS  read-only
    STATUS  current
    DESCRIPTION
        "The first part of initiator name"
    ::=  { rlIscsiSnoopInitiatorNameEntry 2 }

rlIscsiSnoopInitiatorName2 OBJECT-TYPE
    SYNTAX  DisplayString(SIZE(0..63))
    MAX-ACCESS  read-only
    STATUS  current
    DESCRIPTION
        "The second part of initiator name"
    ::=  { rlIscsiSnoopInitiatorNameEntry 3 }



-------------------------------------------------------------------------------
rlIscsiSnoopSessionTable OBJECT-TYPE
    SYNTAX      SEQUENCE OF RlIscsiSnoopSessionEntry
    MAX-ACCESS  not-accessible
    STATUS      current
    DESCRIPTION
       "A table that contains iSCSI sessions.
        It is indexed by Target Name ID, Initiator Name ID and ISID."
    ::= { rlIscsiSnoop 7 }

rlIscsiSnoopSessionEntry OBJECT-TYPE
    SYNTAX      RlIscsiSnoopSessionEntry
    MAX-ACCESS  not-accessible
    STATUS      current
    DESCRIPTION
        "An entry (conceptual row) in the rlIscsiSnoopSessionTable."
    INDEX  { rlIscsiSnoopTargetNameId, rlIscsiSnoopInitiatorNameId,
             rlIscsiSnoopSessionISID }
    ::= { rlIscsiSnoopSessionTable 1 }

RlIscsiSnoopSessionEntry ::= SEQUENCE {
    rlIscsiSnoopSessionISID                     OCTET STRING,
    rlIscsiSnoopSessAgingTime                   INTEGER,
    rlIscsiSnoopSessionUpTime                   INTEGER
}

rlIscsiSnoopSessionISID   OBJECT-TYPE
    SYNTAX         OCTET STRING
    MAX-ACCESS  read-only
    STATUS      current
    DESCRIPTION
            "The ISID of current session."
    ::= { rlIscsiSnoopSessionEntry 1 }

rlIscsiSnoopSessAgingTime OBJECT-TYPE
    SYNTAX      INTEGER
    MAX-ACCESS  read-only
    STATUS      current
    DESCRIPTION
        "The aging time of current session in seconds
         For session not under monitor it is equal max aging time. "
    ::= { rlIscsiSnoopSessionEntry 2 }

rlIscsiSnoopSessionUpTime OBJECT-TYPE
   SYNTAX INTEGER
   MAX-ACCESS read-only
   STATUS current
   DESCRIPTION       "Time the session exists, in seconds."
   ::= { rlIscsiSnoopSessionEntry 3 }


-------------------------------------------------------------------------------
rlIscsiSnoopConnectionTable OBJECT-TYPE
    SYNTAX      SEQUENCE OF RlIscsiSnoopConnectionEntry
    MAX-ACCESS  not-accessible
    STATUS      current
    DESCRIPTION
       "A table that contains iSCSI connections. This is indexed by Session ID and
        TCP connection parameters."
    ::= { rlIscsiSnoop 8 }

rlIscsiSnoopConnectionEntry OBJECT-TYPE
    SYNTAX      RlIscsiSnoopConnectionEntry
    MAX-ACCESS  not-accessible
    STATUS      current
    DESCRIPTION
        "An entry (conceptual row) in the rlIscsiSnoopConnectionTable."
    INDEX  { rlIscsiSnoopTargetNameId, rlIscsiSnoopInitiatorNameId,
             rlIscsiSnoopSessionISID,
             rlIscsiSnoopConnectionTargetAddr,
             rlIscsiSnoopConnectionTargetPort,
             rlIscsiSnoopConnectionInitiatorAddr,
             rlIscsiSnoopConnectionInitiatorPort
}
    ::= { rlIscsiSnoopConnectionTable 1 }

RlIscsiSnoopConnectionEntry ::= SEQUENCE {
    rlIscsiSnoopConnectionTargetAddr                    IpAddress,
    rlIscsiSnoopConnectionTargetPort                    INTEGER,
    rlIscsiSnoopConnectionInitiatorAddr                 IpAddress,
    rlIscsiSnoopConnectionInitiatorPort                 INTEGER,
    rlIscsiSnoopConnectionCreationTime                  TimeStamp,
    rlIscsiSnoopConnectionLastActTime                   TimeStamp,
    rlIscsiSnoopConnectionLastPollTime                  TimeStamp,
    rlIscsiSnoopConnectionExpiryTime                    TimeStamp,
    rlIscsiSnoopConnectionCounterIndex                  Unsigned32
}

 rlIscsiSnoopConnectionTargetAddr OBJECT-TYPE
    SYNTAX      IpAddress
    MAX-ACCESS  not-accessible
    STATUS      current
    DESCRIPTION
        "Specifies the connection target address."
    ::= { rlIscsiSnoopConnectionEntry 2 }

rlIscsiSnoopConnectionTargetPort OBJECT-TYPE
    SYNTAX      INTEGER
    MAX-ACCESS  not-accessible
    STATUS      current
    DESCRIPTION
        "The TCP port of connection target."
    ::= { rlIscsiSnoopConnectionEntry 3 }

 rlIscsiSnoopConnectionInitiatorAddr OBJECT-TYPE
    SYNTAX      IpAddress
    MAX-ACCESS  not-accessible
    STATUS      current
    DESCRIPTION
        "Specifies the connection initiator address."
    ::= { rlIscsiSnoopConnectionEntry 5 }

rlIscsiSnoopConnectionInitiatorPort OBJECT-TYPE
    SYNTAX      INTEGER
    MAX-ACCESS  read-only
    STATUS      current
    DESCRIPTION
        "The TCP port of connection initiator."
    ::= { rlIscsiSnoopConnectionEntry 6 }

rlIscsiSnoopConnectionCreationTime OBJECT-TYPE
    SYNTAX      TimeStamp
    MAX-ACCESS  read-only
    STATUS      current
    DESCRIPTION
        "The value of SysUpTime at which the connection was created."
    ::= { rlIscsiSnoopConnectionEntry 7 }

rlIscsiSnoopConnectionLastActTime OBJECT-TYPE
    SYNTAX      TimeStamp
    MAX-ACCESS  read-only
    STATUS      current
    DESCRIPTION
        "The value of SysUpTime on the most recent occasion at which
         the counter object indexed with the value of
         rlIscsiSnoopConnectionCounterIndex was incremented"
    ::= { rlIscsiSnoopConnectionEntry 8 }

rlIscsiSnoopConnectionLastPollTime OBJECT-TYPE
    SYNTAX      TimeStamp
    MAX-ACCESS  read-only
    STATUS      current
    DESCRIPTION
        "The value of SysUpTime on the most recent occasion at which
         the counter object indexed with the value of
         rlIscsiSnoopConnectionCounterIndex was sampled"
    ::= { rlIscsiSnoopConnectionEntry 9 }

rlIscsiSnoopConnectionExpiryTime OBJECT-TYPE
    SYNTAX      TimeStamp
    MAX-ACCESS  read-only
    STATUS      current
    DESCRIPTION
        "The value of SysUpTime at which the connection should be discarded
         as a result of inactivity elapsed at least rlIscsiSnoopAgingTimeOut."
    ::= { rlIscsiSnoopConnectionEntry 10 }

rlIscsiSnoopConnectionCounterIndex OBJECT-TYPE
    SYNTAX      Unsigned32
    MAX-ACCESS  read-only
    STATUS      current
    DESCRIPTION
        "The index into the the connection counters table
         of the counter object bound to
         this rlIscsiSnoopConnectionEntry object."
    ::= { rlIscsiSnoopConnectionEntry 11 }

--rlIscsiSnoopConnExceeded TRAP-TYPE
--    ENTERPRISE  rnd
--    VARIABLES   { rndErrorDesc, rndErrorSeverity }
--    DESCRIPTION
--        "Warning trap indicating - TCP connection over the max number not inserted."
--   ::= 203


END
