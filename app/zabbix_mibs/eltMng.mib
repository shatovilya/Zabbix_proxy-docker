ELTEX-MES-MNG-MIB DEFINITIONS ::= BEGIN

-- Title:      ELTEX MES Switch Interfaces Private
-- Version:    1.0
-- Date:       21 Sep 2012
-- 21-Sep-2012 - Added eltMesIfExtensionMIB

IMPORTS
    eltMesMng                                              	FROM ELTEX-MES
    MODULE-IDENTITY, OBJECT-TYPE                            FROM SNMPv2-SMI;

eltMesIfExtensionMIB       	OBJECT IDENTIFIER ::= { eltMesMng 276 }

eltMesBridgeExtMIB         	OBJECT IDENTIFIER ::= { eltMesMng 401 }

eltMesSwitchRateLimiterMIB 	OBJECT IDENTIFIER ::= { eltMesMng 773 }

END
