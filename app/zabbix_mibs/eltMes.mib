--
-- Eltex MES Ethernet Switches  MIBs
--
-- Copyright (c) 2015, Eltex Ltd
-- All rights reserved.
--

ELTEX-MES DEFINITIONS ::= BEGIN

IMPORTS
    MODULE-IDENTITY, OBJECT-TYPE, NOTIFICATION-TYPE
        FROM SNMPv2-SMI
    OBJECT-GROUP
        FROM SNMPv2-CONF
    eltexLtd, elHardware
        FROM ELTEX-SMI-ACTUAL;

eltMes MODULE-IDENTITY
    LAST-UPDATED "201511170000Z"
    ORGANIZATION "Eltex Co"
    CONTACT-INFO "eltex.nsk.ru"
    DESCRIPTION  "Mib for Eltex MES ethernet switches."
    REVISION "201511170000Z"
    DESCRIPTION
        "Initial revision."
    ::= { elHardware 23 }

    Percents ::= INTEGER (0..100)
    NetNumber ::=  OCTET STRING (SIZE(4))
    VlanPriority ::= INTEGER (0..7)

-- Some MIB compilers require that the following 7 lines which define the path
-- to Elt MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

--   Objects in this MIB are arranged into groups:
--01 eltMesMng             - Management/Action
--02 ...

-- At the end of the MIB there is a definition of all Eltex-specific traps.

eltMesNotifications OBJECT-IDENTITY
           STATUS      current
           DESCRIPTION " All the Eltex notifications will reside under this branch
                         as specified in
                         RFC2578 'Structure of Management Information Version 2 (SMIv2)' 8.5"
           ::= { eltMes 0 }

-- eltMesMng group contains Management Variables for Eltex devices

eltMesMng   OBJECT IDENTIFIER ::= { eltMes 1  }
-- see eltMng.mib

eltMesCopy   OBJECT IDENTIFIER ::= { eltMes 3  }
-- see eltCopy.mib

eltMesIpOspfMtu   OBJECT IDENTIFIER ::= { eltMes 4  }
-- see eltIpOspfMtu.mib

eltMesLinkAgg   OBJECT IDENTIFIER ::= { eltMes 9  }
-- see eltLinkAgg.mib

eltMesQosTailDropMib   OBJECT IDENTIFIER ::= { eltMes 12  }
-- see eltQosTailDropMib.mib

eltMesSwInterfaces OBJECT IDENTIFIER ::= { eltMes 43  }
-- see eltInterfaces.mib

eltMesPhdTransceiver OBJECT IDENTIFIER ::= { eltMes 53 }
--see ELTEX-PHYSICAL-DESCRIPTION-MIB.mib

eltMesStormCtrl OBJECT IDENTIFIER ::= { eltMes 77 }
--see eltStormCtrl.mib

eltMesRadius  OBJECT IDENTIFIER ::= { eltMes 80 }
--see eltAAA.mib

eltMesQosCliMib OBJECT IDENTIFIER ::= { eltMes 88 }
--see eltQosclimib.mib

eltMesIpSpec OBJECT IDENTIFIER ::= { eltMes 91 }
-- see eltip.mib

eltMesEndOfMibGroup   OBJECT IDENTIFIER ::= { eltMes 1000  }
-- see ELTEX-ENDOFMIB-MIB.MIB



END
