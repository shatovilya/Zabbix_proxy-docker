ELTEX-MES-LINKAGG-MIB DEFINITIONS ::= BEGIN

-- Title:      Eltex MES Link Aggregation Addendum Mib
-- Version:    1.0
-- Date:       31 Aug 2014

IMPORTS
    MODULE-IDENTITY, OBJECT-TYPE, Counter32, TimeTicks
        FROM SNMPv2-SMI
    DisplayString, MacAddress, TEXTUAL-CONVENTION, TruthValue
        FROM SNMPv2-TC
    eltMesLinkAgg
    	FROM ELTEX-MES
    rlDot3adAggBalanceEntry
    	FROM RADLAN-TRUNK-MIB;

eltMesLagMIB MODULE-IDENTITY
    LAST-UPDATED "201408310000Z"
    ORGANIZATION "Eltex Ltd."
    CONTACT-INFO
        "www.eltex.nsk.ru"
    DESCRIPTION
        "The Link Aggregation module IEEE 802.3ad extension."
    ::= { eltMesLinkAgg 1 }

eltMesLagMIBObjects OBJECT IDENTIFIER ::= { eltMesLagMIB 1 }

eltMesLinkAggPort   OBJECT IDENTIFIER ::= { eltMesLagMIBObjects 2 }

--------------------------------------------------------------------------------
-- eltAggBalanceTable
--------------------------------------------------------------------------------

eltAggBalanceTable OBJECT-TYPE
    SYNTAX      SEQUENCE OF EltAggBalanceEntry
    MAX-ACCESS  not-accessible
    STATUS      current
    DESCRIPTION
        "A table that contains Eltex extension of balansing criterion used
         for the corresponding dot3adAggIndex."
    ::= { eltMesLinkAggPort 2 }

eltAggBalanceEntry OBJECT-TYPE
    SYNTAX      EltAggBalanceEntry
    MAX-ACCESS  not-accessible
    STATUS      current
    DESCRIPTION
        "A list of information for each dot3adAggIndex."
    AUGMENTS    { rlDot3adAggBalanceEntry }
    ::= { eltAggBalanceTable 1 }

EltAggBalanceEntry ::= SEQUENCE {
	eltAggBalanceMplsAware 	TruthValue
}

eltAggBalanceMplsAware OBJECT-TYPE
    SYNTAX       TruthValue
    MAX-ACCESS   read-write
    STATUS       current
    DESCRIPTION
        "If this value is TRUE, IP over MPLS traffic will be treated as IP
         traffic instead of as non-IP. Note that this setting will affect all
         device services, not only load balancing. Can't be TRUE if
         rlDot3adAggBalanceLayer equals 2."
    DEFVAL { false }
    ::= { eltAggBalanceEntry 1 }

END
