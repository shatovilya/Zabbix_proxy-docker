MARVELL-SCT-MIB DEFINITIONS ::= BEGIN

-- Title:      Marvell Switch Interfaces Private
-- Version:    7.50
-- Date:       16 Aug 2010

IMPORTS
    OBJECT-TYPE, Counter32                         FROM SNMPv2-SMI
    TruthValue                                      FROM SNMPv2-TC
    rnd                                             FROM RADLAN-MIB;

rlSctMib MODULE-IDENTITY
        LAST-UPDATED "201008161234Z"
        ORGANIZATION "MARVELL Semiconductor, Inc."
        CONTACT-INFO
              "www.marvell.com"
        DESCRIPTION
            "The private MIB module definition for SCT MIB."
        ::= { rnd 203 }

--rlSctCpuRateEnabled
rlSctCpuRateEnabled OBJECT-TYPE
    SYNTAX      TruthValue
    MAX-ACCESS  read-write
    STATUS      current
    DESCRIPTION
        "Indication whether the counter CPU rate is enabled"
    ::= { rlSctMib 1 }

--rlSctCpuRate
rlSctCpuRate OBJECT-TYPE
    SYNTAX      Counter32
    MAX-ACCESS  read-only
    STATUS      current
    DESCRIPTION
        "the amount of packets per second the CPU is handling."
    ::= { rlSctMib 2 }

--rlSctCpuRateTrafficTypeTable
rlSctCpuRateTrafficTypeTable OBJECT-TYPE
    SYNTAX          SEQUENCE OF RlSctCpuRateTrafficTypeEntry
    MAX-ACCESS      not-accessible
    STATUS          current
    DESCRIPTION        "A list of CPU input rates per traffic type."
    ::= { rlSctMib 3 }

rlSctCpuRateTrafficTypeEntry OBJECT-TYPE
    SYNTAX          RlSctCpuRateTrafficTypeEntry
    MAX-ACCESS      not-accessible
    STATUS          current
    DESCRIPTION        "An entry containing the CPU input rates
                        for specific traffic type."
    INDEX           { rlSctCpuRateTrafficTypeIndex }
    ::= { rlSctCpuRateTrafficTypeTable 1 }

RlSctCpuRateTrafficType ::= TEXTUAL-CONVENTION
    STATUS current
    DESCRIPTION    "Traffic types for input rates on CPU."
    SYNTAX INTEGER {
        rlCPUStack(1),
        rlCPUTypeHttp(2),
        rlCPUTypeTelnet(3),
        rlCPUTypeSsh(4),
        rlCPUTypeSnmp(5),
        rlCPUTypeIp(6),
        rlCPUTypeArp(7),
        rlCPUTypeArpInspec(8),
        rlCPUTypeStp(9),
        rlCPUTypeIeee(10),
        rlCPUTypeUdld(11),
        rlCPUTypeCdp(12),
        rlCPUTypeRouteUnknown(13),
        rlCPUTypeIpHopByHop(14),
        rlCPUTypeMtuExceeded(15),
        rlCPUTypeIpv4Multicast(16),
        rlCPUTypeIpv6Multicast(17),
        rlCPUTypeDhcpSnooping(18),
        rlCPUTypeIscsiSnooping(19),
        rlCPUTypeWebAuthSnooping(20),
        rlCPUTypeIgmpSnooping(21),
        rlCPUTypeMldSnooping(22),
        rlCPUTypeTtlExceeded(23),
        rlCPUTypeIpv4IllegalAddress(24),
        rlCPUTypeIpv4HeaderError(25),
        rlCPUTypeIpDaMismatch(26),
        rlCPUTypeSflow(27),
        rlCPUTypeLogDenyAces(28),
        rlCPUTypePtp(29)
}

RlSctCpuRateTrafficTypeEntry ::= SEQUENCE {
        rlSctCpuRateTrafficTypeIndex       RlSctCpuRateTrafficType,
        rlSctCpuRateTrafficTypeRate        Counter32,
        rlSctCpuRateTrafficTypeCounter     Counter32
}

rlSctCpuRateTrafficTypeIndex OBJECT-TYPE
    SYNTAX          RlSctCpuRateTrafficType
    MAX-ACCESS      read-only
    STATUS          current
    DESCRIPTION        "Traffic type"
    ::= { rlSctCpuRateTrafficTypeEntry 1 }

rlSctCpuRateTrafficTypeRate OBJECT-TYPE
    SYNTAX          Counter32
    MAX-ACCESS      read-only
    STATUS          current
    DESCRIPTION        "Input rate int packets per second"
    ::= { rlSctCpuRateTrafficTypeEntry 2 }

rlSctCpuRateTrafficTypeCounter OBJECT-TYPE
    SYNTAX          Counter32
    MAX-ACCESS      read-only
    STATUS          current
    DESCRIPTION        "Total counter of packets"
    ::= { rlSctCpuRateTrafficTypeEntry 3 }

END
