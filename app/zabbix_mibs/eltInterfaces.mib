ELTEX-MES-eltInterfaces DEFINITIONS ::= BEGIN

-- Title:      ELTEX MES Switch Interfaces Private
-- Version:    1.0
-- Date:       14 Aug 2012
-- 14-Aug-2012 - Added SFP operation mode

IMPORTS
    eltMesSwInterfaces                                      FROM ELTEX-MES
    ifIndex, InterfaceIndex, InterfaceIndexOrZero           FROM IF-MIB
    PortList                                                FROM Q-BRIDGE-MIB
    Unsigned32, Integer32, Counter32,
    MODULE-IDENTITY, OBJECT-TYPE                            FROM SNMPv2-SMI
    Counter                                                 FROM RFC1155-SMI
    RowStatus                                               FROM SNMPv2-TC;

--
-- Ports utilization table mib
--
eltSwIfUtilizationTable OBJECT-TYPE
   SYNTAX  SEQUENCE  OF EltSwIfUtilizationEntry
   MAX-ACCESS   not-accessible
   STATUS       current
   DESCRIPTION
    "Switch ports utilization configuration and information."
   ::=  { eltMesSwInterfaces 2 }

eltSwIfUtilizationEntry OBJECT-TYPE
   SYNTAX  EltSwIfUtilizationEntry
   MAX-ACCESS   not-accessible
   STATUS       current
   DESCRIPTION
    "Defines the contents of each line in the eltSwIfUtilizationTable table."
   INDEX   { eltSwIfUtilizationIfIndex }
   ::=  { eltSwIfUtilizationTable 1 }

EltSwIfUtilizationEntry ::= SEQUENCE {
        eltSwIfUtilizationIfIndex               INTEGER,
        eltSwIfUtilizationAverageTime           INTEGER,
        eltSwIfUtilizationCurrentInPkts         Counter,
        eltSwIfUtilizationCurrentInRate         Counter,
        eltSwIfUtilizationCurrentOutPkts        Counter,
        eltSwIfUtilizationCurrentOutRate        Counter,
        eltSwIfUtilizationAverageInPkts         Counter,
        eltSwIfUtilizationAverageInRate         Counter,
        eltSwIfUtilizationAverageOutPkts        Counter,
        eltSwIfUtilizationAverageOutRate        Counter
	}

eltSwIfUtilizationIfIndex OBJECT-TYPE
   SYNTAX  INTEGER
   MAX-ACCESS  read-only
   STATUS  current
   DESCRIPTION
          "A unique value for each interface.  Its value
          ranges between 1 and the value of ifNumber.  The
          value for each interface must remain constant at
          least from one re-initialization of the entity's
          network management system to the next re-
          initialization."
   ::= { eltSwIfUtilizationEntry 1 }

eltSwIfUtilizationAverageTime OBJECT-TYPE
   SYNTAX  INTEGER
   MAX-ACCESS  read-write
   STATUS  current
   DESCRIPTION
          "An average load time in seconds for which interface
          utilization is calculated."
   ::= { eltSwIfUtilizationEntry 2 }

eltSwIfUtilizationCurrentInPkts OBJECT-TYPE
   SYNTAX  Counter
   MAX-ACCESS  read-only
   STATUS  current
   DESCRIPTION
          "The total number of all (UC, MC and BC) packets
          received on the interface during last 5 seconds."
  ::= { eltSwIfUtilizationEntry 3 }

eltSwIfUtilizationCurrentInRate OBJECT-TYPE
   SYNTAX  Counter
   MAX-ACCESS  read-only
   STATUS  current
   DESCRIPTION
          "The inbound rate in kbit/sec
          on the interface during last 5 seconds."
  ::= { eltSwIfUtilizationEntry 4 }

eltSwIfUtilizationCurrentOutPkts OBJECT-TYPE
   SYNTAX  Counter
   MAX-ACCESS  read-only
   STATUS  current
   DESCRIPTION
          "The total number of all (UC, MC and BC) packets
          sent out of the interface during last 5 seconds."
  ::= { eltSwIfUtilizationEntry 5 }

eltSwIfUtilizationCurrentOutRate OBJECT-TYPE
   SYNTAX  Counter
   MAX-ACCESS  read-only
   STATUS  current
   DESCRIPTION
          "The outbound rate in kbit/sec
          on the interface during last 5 seconds."
  ::= { eltSwIfUtilizationEntry 6 }

eltSwIfUtilizationAverageInPkts OBJECT-TYPE
   SYNTAX  Counter
   MAX-ACCESS  read-only
   STATUS  current
   DESCRIPTION
          "The total number of all (UC, MC and BC) packets
          received on the interface during configured
          load average time for this interface."
  ::= { eltSwIfUtilizationEntry 7 }

eltSwIfUtilizationAverageInRate OBJECT-TYPE
   SYNTAX  Counter
   MAX-ACCESS  read-only
   STATUS  current
   DESCRIPTION
          "The inbound rate in kbit/sec on the interface
          during configured load average time for this interface."
  ::= { eltSwIfUtilizationEntry 8 }

eltSwIfUtilizationAverageOutPkts OBJECT-TYPE
   SYNTAX  Counter
   MAX-ACCESS  read-only
   STATUS  current
   DESCRIPTION
          "The total number of all (UC, MC and BC) packets
          sent out of the interface during configured
          load average time for this interface."
  ::= { eltSwIfUtilizationEntry 9 }

eltSwIfUtilizationAverageOutRate OBJECT-TYPE
   SYNTAX  Counter
   MAX-ACCESS  read-only
   STATUS  current
   DESCRIPTION
          "The outbound rate in kbit/sec on the interface
          during configured load average time for this interface."
  ::= { eltSwIfUtilizationEntry 10 }

END
