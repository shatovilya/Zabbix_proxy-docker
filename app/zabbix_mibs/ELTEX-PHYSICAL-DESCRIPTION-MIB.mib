ELTEX-MES-PHYSICAL-DESCRIPTION-MIB DEFINITIONS ::= BEGIN
-- Version:              1.0
-- Date:                 21-Mar-2013

IMPORTS
    OBJECT-TYPE, MODULE-IDENTITY, TimeTicks,
    NOTIFICATION-TYPE, Integer32                            FROM SNMPv2-SMI
    DisplayString, PhysAddress, RowStatus, TruthValue       FROM SNMPv2-TC
    JackType                                                FROM MAU-MIB
    InterfaceIndexOrZero,ifIndex,InterfaceIndex             FROM IF-MIB
    eltMes                                                  FROM ELTEX-MES
    ;

eltMesPhysicalDescription  MODULE-IDENTITY
                       LAST-UPDATED "201303210000Z"
                       ORGANIZATION "Eltex Ltd."
                       CONTACT-INFO
                            "eltex.nsk.ru"
                       DESCRIPTION
                            "The private MIB module definition for physical
                             device configuration and information."
                       REVISION "201303210000Z"
                       DESCRIPTION
                            "Initial revision."
                       ::= { eltMes 53 }

eltMesPhdTransceiver OBJECT IDENTIFIER ::= { eltMesPhysicalDescription 1 }

eltPhdTransceiverInfoTable OBJECT-TYPE
    SYNTAX SEQUENCE OF EltPhdTransceiverInfoEntry
    MAX-ACCESS not-accessible
    STATUS current
    DESCRIPTION
        "This table show the information of transceiver on interface."
    ::= { eltMesPhdTransceiver 1 }

eltPhdTransceiverInfoEntry OBJECT-TYPE
    SYNTAX EltPhdTransceiverInfoEntry
    MAX-ACCESS not-accessible
    STATUS current
    DESCRIPTION
        "The entry of the eltPhdTransceiverInfoTable."
    INDEX { ifIndex }
    ::= { eltPhdTransceiverInfoTable 1 }

EltPhdTransceiverInfoEntry ::=
    SEQUENCE {
        eltPhdTransceiverInfoConnectorType         INTEGER,
        eltPhdTransceiverInfoType                  INTEGER,
        eltPhdTransceiverInfoComplianceCode        OCTET STRING,
        eltPhdTransceiverInfoWaveLength            Integer32,
        eltPhdTransceiverInfoVendorName            OCTET STRING,
        eltPhdTransceiverInfoSerialNumber          OCTET STRING,
        eltPhdTransceiverInfoFiberDiameterType     INTEGER,
        eltPhdTransceiverInfoTransferDistance      Integer32,
        eltPhdTransceiverInfoDiagnostic            TruthValue
    }

eltPhdTransceiverInfoConnectorType OBJECT-TYPE
    SYNTAX INTEGER
        {
            unknown(0),
            sc(1),
            fibre-ch-st1(2),
            fibre-ch-st2(3),
            bnc-tnc(4),
            fibre-ch-coaxial-headers(5),
            fibrejack(6),
            lc(7),
            mt-rj(8),
            mu(9),
            sg(10),
            optical-pigtail(11),
            mpo-parallel-optic(12),
            hssdc-ii(32),
            copper-pigtail(33),
            rj45(34),
            unallocated(127),
            vendorspec(255)
        }
    MAX-ACCESS read-only
    STATUS current
    DESCRIPTION
        "Connector type of the interface."
    ::= { eltPhdTransceiverInfoEntry 1 }

eltPhdTransceiverInfoType OBJECT-TYPE
    SYNTAX INTEGER
            {
            unknown(0),
            gbic(1),
            sff(2),
            sfp-sfpplus(3),
            xbi-300-pin(4),
            xenpak(5),
            xfp(6),
            xff(7),
            xfp-e(8),
            xpak(9),
            x2(10),
            dwdm-sfp(11),
            qsfp(12),
            reserved(127),
            vendorspec(255)
            }
    MAX-ACCESS read-only
    STATUS current
    DESCRIPTION
        "Type of the interface, such as SFP/XFP/GBIC."
    ::= { eltPhdTransceiverInfoEntry 2 }

eltPhdTransceiverInfoComplianceCode OBJECT-TYPE
    SYNTAX OCTET STRING
    MAX-ACCESS read-only
    STATUS current
    DESCRIPTION
        "Compliance code read from the transceiver."
    ::= { eltPhdTransceiverInfoEntry 3 }

eltPhdTransceiverInfoWaveLength OBJECT-TYPE
    SYNTAX Integer32
    MAX-ACCESS read-only
    STATUS current
    DESCRIPTION
        "Wave length of the interface, measured in nanometer."
    ::= { eltPhdTransceiverInfoEntry 4 }

eltPhdTransceiverInfoVendorName OBJECT-TYPE
    SYNTAX OCTET STRING
    MAX-ACCESS read-only
    STATUS current
    DESCRIPTION
        "Vendor name of the interface."
    ::= { eltPhdTransceiverInfoEntry 5 }

eltPhdTransceiverInfoSerialNumber OBJECT-TYPE
    SYNTAX OCTET STRING
    MAX-ACCESS read-only
    STATUS current
    DESCRIPTION
        "Serial number of the interface."
    ::= { eltPhdTransceiverInfoEntry 6 }

eltPhdTransceiverInfoFiberDiameterType OBJECT-TYPE
    SYNTAX INTEGER
        {
          fiber9(1),
          fiber50(2),
          fiber625(3),
          copper(4),
          unknown(65535)
        }
    MAX-ACCESS read-only
    STATUS current
    DESCRIPTION
        "The diameter of the fiber, measured in micron.
        fiber9 - 9 micron multi-mode fiber
        fiber50 - 50 micron multi-mode fiber
        fiber625 - 62.5 micron multi-mode fiber
        copper - copper cable."
    ::= { eltPhdTransceiverInfoEntry 7 }

eltPhdTransceiverInfoTransferDistance OBJECT-TYPE
    SYNTAX Integer32
    MAX-ACCESS read-only
    STATUS current
    DESCRIPTION
        "The maximal distance which the interface could transmit,
        measured in meter."
    ::= { eltPhdTransceiverInfoEntry 8 }

eltPhdTransceiverInfoDiagnostic OBJECT-TYPE
    SYNTAX      TruthValue
    MAX-ACCESS  read-only
    STATUS      current
    DESCRIPTION
        "Indicating whether the digital diagnostic monitoring function is supported or not."
    ::= { eltPhdTransceiverInfoEntry 9 }

END
