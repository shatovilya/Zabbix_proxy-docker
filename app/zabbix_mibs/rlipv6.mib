RADLAN-IPv6 DEFINITIONS ::= BEGIN

-- Title:      RADLAN IPv6 Private Extension
-- Version:    7.46.00.00
-- Date:       25 Jan 2007

IMPORTS
    MODULE-IDENTITY, OBJECT-TYPE,
    Integer32, Counter32, IpAddress,
    mib-2, Unsigned32, Counter64,
    zeroDotZero                        FROM SNMPv2-SMI
    TimeInterval, TruthValue           FROM SNMPv2-TC
    rnd                                FROM RADLAN-MIB
    ipSpec                             FROM RADLAN-IP
    ipAddressEntry, ipv6InterfaceEntry FROM IP-MIB
    ipNetToPhysicalEntry               FROM IP-MIB
    inetCidrRouteEntry                 FROM IP-FORWARD-MIB
    InterfaceIndexOrZero               FROM IF-MIB
    InetAddressPrefixLength            FROM INET-ADDRESS-MIB;


rlIPv6  MODULE-IDENTITY
        LAST-UPDATED "200809250000Z"
        ORGANIZATION "Marvell Semiconductor, Inc."
        CONTACT-INFO
                    "www.marvell.com"
        DESCRIPTION
                "The private MIB module definition for IPv6 MIB."
        REVISION "200809250000Z"
        DESCRIPTION
                "Initial version of this MIB."
        ::= { rnd 129 }


--- IpAddressTable augmentation

rlIpAddressTable OBJECT-TYPE
    SYNTAX     SEQUENCE OF RlIpAddressEntry
    MAX-ACCESS not-accessible
    STATUS     current
    DESCRIPTION
           "This table is parallel to ipAddressTable, and is used to
            add/delete IPv6 entries to/from that table. It contains
            private objects."
    ::= { ipSpec 19 }

rlIpAddressEntry OBJECT-TYPE
    SYNTAX     RlIpAddressEntry
    MAX-ACCESS not-accessible
    STATUS     current
    DESCRIPTION
           "An address mapping for a particular interface."
    AUGMENTS { ipAddressEntry }
    ::= { rlIpAddressTable 1 }

RlIpAddressEntry ::= SEQUENCE {
        rlIpAddressPrefixLength   InetAddressPrefixLength,
        rlIpAddressType           INTEGER
    }

rlIpAddressPrefixLength OBJECT-TYPE
    SYNTAX     InetAddressPrefixLength
    MAX-ACCESS read-create
    STATUS     current
    DESCRIPTION
           "The prefix length of this address."
    DEFVAL { 0 }
    ::= { rlIpAddressEntry 1 }

rlIpAddressType OBJECT-TYPE
    SYNTAX     INTEGER {
                 unicast(1),
                 anycast(2),
                 broadcast(3),
                 multicast(4)
    }
    MAX-ACCESS read-only
    STATUS     current
    DESCRIPTION
           "Extend standard field ipAddressType to multicast"
    DEFVAL { unicast }
    ::= { rlIpAddressEntry 2 }


--- ipv6InterfaceTable augmentation

rlipv6InterfaceTable OBJECT-TYPE
    SYNTAX     SEQUENCE OF Rlipv6InterfaceEntry
    MAX-ACCESS not-accessible
    STATUS     current
    DESCRIPTION
           "This table is parallel to ipv6InterfaceTable, and is used to
            configure additional interface parameters."
    ::= { ipSpec 20 }

rlipv6InterfaceEntry OBJECT-TYPE
    SYNTAX     Rlipv6InterfaceEntry
    MAX-ACCESS not-accessible
    STATUS     current
    DESCRIPTION
           "Additional configuration parameters for a particular interface."
    AUGMENTS { ipv6InterfaceEntry }
    ::= { rlipv6InterfaceTable 1 }

Rlipv6InterfaceEntry ::= SEQUENCE {
        rlipv6InterfaceNdDadAttemps             INTEGER,
        rlipv6InterfaceAutoconfigEnable         INTEGER,
        rlipv6InterfaceIcmpUnreachSendEnable    INTEGER,
        rlipv6InterfaceLinkMTU                  Unsigned32,
        rlipv6InterfaceMLDVersion               Unsigned32
    }

rlipv6InterfaceNdDadAttemps OBJECT-TYPE
    SYNTAX     INTEGER (0..600)
    MAX-ACCESS read-create
    STATUS     current
    DESCRIPTION
           "ND Duplicated address detection number of attempts."
    DEFVAL { 0 }
    ::= { rlipv6InterfaceEntry 1 }

rlipv6InterfaceAutoconfigEnable OBJECT-TYPE
    SYNTAX  INTEGER {
        enable(1),
        disable(2)
    }
    MAX-ACCESS  read-create
    STATUS      current
    DESCRIPTION
        "Enables or disables Stateless Address Auto configuration
         on specific interface."
    DEFVAL { enable }
    ::=  { rlipv6InterfaceEntry 2 }

rlipv6InterfaceIcmpUnreachSendEnable OBJECT-TYPE
    SYNTAX  INTEGER {
        enable(1),
        disable(2)
    }
    MAX-ACCESS  read-create
    STATUS      current
    DESCRIPTION
        "Enables or disables sending of ICMP Destination Unreachable
         Error on specific interface."
    DEFVAL { enable }
       ::= { rlipv6InterfaceEntry 3 }

rlipv6InterfaceLinkMTU OBJECT-TYPE
    SYNTAX     Unsigned32 (1280..65535)
    MAX-ACCESS read-create
    STATUS     current
    DESCRIPTION
           "The maximum transmission unit (MTU) size of IPv6 packets
            sent on an interface in bytes."
    DEFVAL { 1500 }
    ::= { rlipv6InterfaceEntry 4 }

rlipv6InterfaceMLDVersion OBJECT-TYPE
    SYNTAX  Unsigned32 (1..2)
    MAX-ACCESS  read-create
    STATUS      current
    DESCRIPTION
        "Set version of MLD protocol on specific interface."
    DEFVAL { 2 }
    ::=  { rlipv6InterfaceEntry 5 }


--- inetCidrRoutetable augmentation

rlinetCidrRouteTable OBJECT-TYPE
    SYNTAX     SEQUENCE OF RlinetCidrRouteEntry
    MAX-ACCESS not-accessible
    STATUS     current
    DESCRIPTION
           "This table is parallel to inetCidrRouteTable, and is used to
            configure or display additional route parameters."
    ::= { ipSpec 21 }

rlinetCidrRouteEntry OBJECT-TYPE
    SYNTAX     RlinetCidrRouteEntry
    MAX-ACCESS not-accessible
    STATUS     current
    DESCRIPTION
           "Additional parameters for a particular route."
    AUGMENTS { inetCidrRouteEntry }
    ::= { rlinetCidrRouteTable 1 }

RlinetCidrRouteEntry ::= SEQUENCE {
        rlinetCidrRouteLifetime         Unsigned32
    }

rlinetCidrRouteLifetime OBJECT-TYPE
    SYNTAX     Unsigned32
    UNITS      "seconds"
    MAX-ACCESS read-only
    STATUS     current
    DESCRIPTION
           "The remaining length of time, in seconds, that this route
            will continue to be valid, i.e., time until deprecation.
            A value of 4,294,967,295 represents infinity."
    DEFVAL { 4294967295 }
    ::= { rlinetCidrRouteEntry 1 }


--- ipNetToPhysicalTable augmentation

rlipNetToPhysicalTable OBJECT-TYPE
    SYNTAX     SEQUENCE OF RlipNetToPhysicalEntry
    MAX-ACCESS not-accessible
    STATUS     current
    DESCRIPTION
           "This table is parallel to ipNetToPhysicalTable, and is used to
            configure or display additional neighbor parameters."
    ::= { ipSpec 22 }

rlipNetToPhysicalEntry OBJECT-TYPE
    SYNTAX     RlipNetToPhysicalEntry
    MAX-ACCESS not-accessible
    STATUS     current
    DESCRIPTION
           "Additional parameters for a neighbor"
    AUGMENTS { ipNetToPhysicalEntry }
    ::= { rlipNetToPhysicalTable 1 }

RlipNetToPhysicalEntry ::= SEQUENCE {
        rlipNetToPhysicalIsRouter       TruthValue
    }

rlipNetToPhysicalIsRouter OBJECT-TYPE
    SYNTAX     TruthValue
    MAX-ACCESS read-only
    STATUS     current
    DESCRIPTION
           "This object has the value 'true(1)', if the neighbor
            is router; otherwise, the value is 'false(2)'."
    ::= { rlipNetToPhysicalEntry 1 }


--- ICMPv6 Rate Limiting

rlipv6IcmpErrorRatelimitInterval OBJECT-TYPE
    SYNTAX      TimeInterval
    MAX-ACCESS  read-write
    STATUS      current
    DESCRIPTION
        "The time interval between tokens being placed in the bucket,
         each token represents a single ICMP error message.
         The interval measured in milliseconds."
    DEFVAL { 100 }
    ::= { rlIPv6 1 }

rlipv6IcmpErrorRatelimitBucketSize OBJECT-TYPE
    SYNTAX      INTEGER(1..200)
    MAX-ACCESS  read-write
    STATUS      current
    DESCRIPTION
        "The maximum number of tokens stored in the bucket,
         each token represents a single ICMP error message."
    DEFVAL { 10 }
    ::= { rlIPv6 2 }


--- IPv6 Link Local Default Zone

rlipv6LLDefaultZone OBJECT-TYPE
    SYNTAX      InterfaceIndexOrZero
    MAX-ACCESS  read-write
    STATUS      current
    DESCRIPTION
        "The interface which would be used as the egress interface
        for packets sent without a specified IPv6Z interface identifier
        or with the default '0' identifier. Zero value means no default
        interface specified."
    DEFVAL { 0 }
    ::= { rlIPv6 3 }


END
