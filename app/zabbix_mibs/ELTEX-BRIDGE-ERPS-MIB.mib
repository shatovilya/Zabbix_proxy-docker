-- -----------------------------------------------------------------------------
-- MIB NAME : ERPS (ITU-T G.8032) Common mib
-- FILE NAME: ELTEX-BRIDGE-ERPS-MIB.mib
-- DATE     : 2013/04/22
-- VERSION  : 1.00
-- PURPOSE  : To construct the MIB structure of ERPS for proprietary enterprise
-- -----------------------------------------------------------------------------

ELTEX-MES-BRIDGE-ERPS-MIB DEFINITIONS ::= BEGIN


    IMPORTS
              MODULE-IDENTITY, OBJECT-TYPE
                    FROM SNMPv2-SMI
              RowStatus,MacAddress,TruthValue
                    FROM SNMPv2-TC
              NOTIFICATION-TYPE
                    FROM SNMPv2-SMI
              VlanIdOrNone
              		FROM Q-BRIDGE-MIB
              eltMesBridgeExtMIBObjects
					FROM ELTEX-MES-BRIDGE-EXT-MIB;

    eltMesErpsMIB MODULE-IDENTITY
        LAST-UPDATED "201512120000Z"    -- 12/12/2015 00:00GMT
        ORGANIZATION "Eltex Ltd."
        CONTACT-INFO
            "http://www.eltex.nsk.ru"
        DESCRIPTION
            "The MIB module for managing Ethernet Ring Protection Switching."
            
        REVISION     "201512120000Z"    -- 12/12/2015 00:00GMT
        DESCRIPTION
            "Deprecate all objects in this module."            
        ::= { eltMesBridgeExtMIBObjects 1 }

    eltMesErpsCtrl                OBJECT IDENTIFIER ::= { eltMesErpsMIB 1 }
    eltMesErpsInfo                OBJECT IDENTIFIER ::= { eltMesErpsMIB 2 }
    eltMesErpsMgmt                OBJECT IDENTIFIER ::= { eltMesErpsMIB 3 }
    eltMesErpsNotify              OBJECT IDENTIFIER ::= { eltMesErpsMIB 4 }

-- -----------------------------------------------------------------------------
-- Textual conventions
-- -----------------------------------------------------------------------------

EltErpsEnabledState ::= TEXTUAL-CONVENTION
    STATUS      deprecated
    DESCRIPTION
       "Indicates whether the state of object is enabled or disabled.
       "
    REFERENCE
       "ITU-T G.8032"
    SYNTAX      INTEGER {
                  enabled  (1),
                  disabled (2)
                }

EltErpsMgmtRAPSPortState ::= TEXTUAL-CONVENTION
    STATUS      deprecated
    DESCRIPTION
       "Indicates Ethernet ring port state.
       "
    REFERENCE
       "ITU-T G.8032"
    SYNTAX      INTEGER {
	                fowarding(1),
	                blocking(2),
	                signal-fail(3),
                    manual-switch(4),
                    forced-switch(5)
                }

EltErpsMgmtRAPSPortId ::= TEXTUAL-CONVENTION
    STATUS      deprecated
    DESCRIPTION
       "Ethernet ring port id.
       "
    REFERENCE
       "ITU-T G.8032"
    SYNTAX      INTEGER {
	                none(1),
	                west(2),
	                east(3)
                }

-- -----------------------------------------------------------------------------
-- eltMesErpsCtrl
-- -----------------------------------------------------------------------------
    eltErpsAdminState OBJECT-TYPE
        SYNTAX  EltErpsEnabledState
        MAX-ACCESS  read-write
        STATUS  deprecated
        DESCRIPTION
            "This object indicates the ERPS state of the bridge."
		DEFVAL  { disabled }
        ::= { eltMesErpsCtrl 1 }

    eltErpsLogState OBJECT-TYPE
        SYNTAX   EltErpsEnabledState
        MAX-ACCESS  read-write
        STATUS      deprecated
        DESCRIPTION
            "This object indicates the ERPS log state of the bridge."
		DEFVAL  { enabled }
        ::= { eltMesErpsCtrl 2 }

    eltErpsTrapState OBJECT-TYPE
        SYNTAX   EltErpsEnabledState
        MAX-ACCESS  read-write
        STATUS      deprecated
        DESCRIPTION
            "This object indicates the ERPS trap state of the bridge."
		DEFVAL  { enabled }
        ::= { eltMesErpsCtrl 3 }
--
--	eltErpsVersion OBJECT-TYPE
--        SYNTAX   INTEGER (1|2)
--        MAX-ACCESS  read-write
--        STATUS      deprecated
--        DESCRIPTION
--            "This object indicates the ERPS protocol compatibility with other versions of ITU-T G.8032."
--		DEFVAL  { 2 }
--        ::= { eltMesErpsCtrl 4 }
--
	eltErpsPendingAction OBJECT-TYPE
	    SYNTAX  INTEGER {
	        copyPendingActive(1),
	        copyActivePending(2)
	    }
	    MAX-ACCESS  read-write
	    STATUS  deprecated
	    DESCRIPTION
	        "The action to be done with the pending configuration.
	         copyPendingActive - to copy the pending erps configuration to the active one.
	         copyActivePending - to copy the active erps configuration to the pending one. "
	    ::= { eltMesErpsCtrl 5 }

	eltErpsPendingActionVlan OBJECT-TYPE
        SYNTAX      INTEGER
        MAX-ACCESS  read-write
        STATUS      deprecated
		DESCRIPTION
            "Variable is associated with eltErpsPendingAction and determines vlan_tag
             number in config for action copying/revert on pending config"
        ::= { eltMesErpsCtrl 6 }

	eltErpsGetConfigId OBJECT-TYPE
        SYNTAX      INTEGER{
    		active(1),
	        pending(2)
        }
        MAX-ACCESS  read-write
        STATUS      deprecated
		DESCRIPTION
            "Set config id fot snmp get."
        ::= { eltMesErpsCtrl 7 }

-- -----------------------------------------------------------------------------
-- eltMesErpsInfo
-- -----------------------------------------------------------------------------

-- -----------------------------------------------------------------------------
-- eltMesErpsMgmt
-- -----------------------------------------------------------------------------

    eltErpsMgmtRAPSVlanTable OBJECT-TYPE
        SYNTAX      SEQUENCE OF EltErpsMgmtRAPSVlanEntry
        MAX-ACCESS  not-accessible
        STATUS      deprecated
        DESCRIPTION
            "This table contains ERPS ring configuration information."
        ::= { eltMesErpsMgmt 1 }

    eltErpsMgmtRAPSVlanEntry OBJECT-TYPE
        SYNTAX      EltErpsMgmtRAPSVlanEntry
        MAX-ACCESS  not-accessible
        STATUS      deprecated
        DESCRIPTION
            "A list of ERPS ring configuration information."
        INDEX    {eltErpsMgmtRAPSVlanId}
        ::= { eltErpsMgmtRAPSVlanTable 1 }

    EltErpsMgmtRAPSVlanEntry ::= SEQUENCE {
            eltErpsMgmtRAPSVlanId
                INTEGER,
            eltErpsMgmtRAPSWestPort
                INTEGER,
            eltErpsMgmtRAPSWestPortState
                EltErpsMgmtRAPSPortState,
            eltErpsMgmtRAPSEastPort
                INTEGER,
            eltErpsMgmtRAPSEastPortState
                EltErpsMgmtRAPSPortState,
            eltErpsMgmtRAPSRPLPort
                EltErpsMgmtRAPSPortId,
            eltErpsMgmtRAPSRPLOwnerAdminState
                EltErpsEnabledState,
            eltErpsMgmtRAPSRingMEL
                INTEGER,
            eltErpsMgmtRAPSHoldOffTime
                INTEGER,
            eltErpsMgmtRAPSGuardTime
                INTEGER,
            eltErpsMgmtRAPSWTRTime
                INTEGER,
            eltErpsMgmtRAPSRingState
                INTEGER,
            eltErpsMgmtRAPSRingAdminState
                EltErpsEnabledState,
            eltErpsMgmtRAPSRPLOwnerOperStatus
                INTEGER,
            eltErpsMgmtRAPSProtectionVlanRangeList1to1024
                OCTET STRING,
            eltErpsMgmtRAPSProtectionVlanRangeList1025to2048
                OCTET STRING,
            eltErpsMgmtRAPSProtectionVlanRangeList2049to3072
                OCTET STRING,
            eltErpsMgmtRAPSProtectionVlanRangeList3073to4094
                OCTET STRING,
            eltErpsMgmtRAPSRevertive
            	TruthValue,
            eltErpsMgmtRAPSProtocolVersion
            	INTEGER,
            eltErpsMgmtRAPSPortForcedSwitch
                EltErpsMgmtRAPSPortId,
            eltErpsMgmtRAPSPortManualSwitch
                EltErpsMgmtRAPSPortId,
            eltErpsMgmtRAPSRowStatus
                RowStatus
        }

    eltErpsMgmtRAPSVlanId  OBJECT-TYPE
        SYNTAX      INTEGER
        MAX-ACCESS  read-only
        STATUS      deprecated
        DESCRIPTION
            "The RAPS VLAN is an index of configuration."
        ::= { eltErpsMgmtRAPSVlanEntry 1 }

    eltErpsMgmtRAPSWestPort OBJECT-TYPE
        SYNTAX  INTEGER (0|1..65535)
        MAX-ACCESS  read-write
        STATUS  deprecated
        DESCRIPTION
            "This is one of the Ethernet ring ports.
            The value 0 indicates the west port is a virtual channel.
           "
		DEFVAL  { 0 }
        ::= { eltErpsMgmtRAPSVlanEntry 2 }

    eltErpsMgmtRAPSWestPortState OBJECT-TYPE
        SYNTAX EltErpsMgmtRAPSPortState
        MAX-ACCESS  read-only
        STATUS  deprecated
        DESCRIPTION
            "This is the west port state. It may change sometimes. When the west port
            is configured on a virtual channel, the west port state is always fowarding.
           "
        ::= { eltErpsMgmtRAPSVlanEntry 3 }

    eltErpsMgmtRAPSEastPort OBJECT-TYPE
        SYNTAX  INTEGER (0|1..65535)
        MAX-ACCESS  read-write
        STATUS  deprecated
        DESCRIPTION
            "This is the other Ethernet ring port.
            The value 0 indicates the west port is a virtual channel.
           "
		DEFVAL  { 0 }
        ::= { eltErpsMgmtRAPSVlanEntry 4 }

    eltErpsMgmtRAPSEastPortState OBJECT-TYPE
		SYNTAX EltErpsMgmtRAPSPortState
        MAX-ACCESS  read-only
        STATUS  deprecated
        DESCRIPTION
            "This is the east port state. It may change sometimes. When the east port
            is configured on a virtual channel, the east port state is always fowarding.
           "
        ::= { eltErpsMgmtRAPSVlanEntry 5 }

    eltErpsMgmtRAPSRPLPort OBJECT-TYPE
        SYNTAX EltErpsMgmtRAPSPortId
        MAX-ACCESS  read-write
        STATUS  deprecated
        DESCRIPTION
            "When the port Enable state is enabled, the RPL port's current port role is defined by the application of the ERPS.
           "
		DEFVAL  { none }
        ::= { eltErpsMgmtRAPSVlanEntry 6 }

    eltErpsMgmtRAPSRPLOwnerAdminState OBJECT-TYPE
        SYNTAX      EltErpsEnabledState
        MAX-ACCESS  read-write
        STATUS      deprecated
        DESCRIPTION
            "The administrative value of the RPL owner state.
             The RPL owner is an Ethernet Ring Node adjacent to the RPL that
             is responsible for blocking its end of the RPL under normal
             conditions."
		DEFVAL  { disabled }
        ::= { eltErpsMgmtRAPSVlanEntry 7 }

    eltErpsMgmtRAPSRingMEL OBJECT-TYPE
        SYNTAX      INTEGER (0..7)
        MAX-ACCESS  read-write
        STATUS      deprecated
        DESCRIPTION
            "The ring MEL is the maintenance entity group (MEG) level providing a communication channel for
                ring automatic protection eltitching (RAPS) information."
		DEFVAL  { 1 }
        ::= { eltErpsMgmtRAPSVlanEntry 8 }

    eltErpsMgmtRAPSHoldOffTime OBJECT-TYPE
        SYNTAX      INTEGER (0..10000)
        MAX-ACCESS  read-write
        STATUS      deprecated
        DESCRIPTION
            "In order to coordinate timing of protection eltitches at multiple layers."
		DEFVAL  { 0 }
        ::= { eltErpsMgmtRAPSVlanEntry 9 }

    eltErpsMgmtRAPSGuardTime OBJECT-TYPE
            SYNTAX      INTEGER (10..2000)
            MAX-ACCESS  read-write
            STATUS      deprecated
            DESCRIPTION
                "This is used to prevent ring nodes from receiving outdated RAPS messages."
		DEFVAL  { 500 }
            ::= { eltErpsMgmtRAPSVlanEntry 10 }

    eltErpsMgmtRAPSWTRTime OBJECT-TYPE
        SYNTAX      INTEGER (1..12)
        MAX-ACCESS  read-write
        STATUS      deprecated
        DESCRIPTION
                "In the revertive mode of operation, to prevent frequent operation of the protection eltitch due to an
                intermittent defect, a failed working transport entity must become stable in a fault-free state."
		DEFVAL  { 5 }
        ::= { eltErpsMgmtRAPSVlanEntry 11 }

    eltErpsMgmtRAPSRingState OBJECT-TYPE
        SYNTAX      INTEGER {
	        init(1),
	        idle(2),
	        protection(3),
	        manual-switch(4),
	        forced-switch(5),
	        pending(6)

        }
        MAX-ACCESS  read-only
        STATUS      deprecated
        DESCRIPTION
                "This indicates the state of the ring: begin, init, idle, or protection."
        ::= { eltErpsMgmtRAPSVlanEntry 12 }

    eltErpsMgmtRAPSRingAdminState OBJECT-TYPE
	    SYNTAX      EltErpsEnabledState
	    MAX-ACCESS  read-write
	    STATUS      deprecated
	    DESCRIPTION
                "This indicates the administrative state of the ring."
		DEFVAL  { disabled }
	    ::= { eltErpsMgmtRAPSVlanEntry 13 }

    eltErpsMgmtRAPSRPLOwnerOperStatus OBJECT-TYPE
        SYNTAX      INTEGER {
					active(1),
					inactive(2),
					disabled(3)
                   }
        MAX-ACCESS  read-only
        STATUS      deprecated
        DESCRIPTION
            "The current operational value of the RPL owner state. The value 'active'
             is used to indicate that the RPL owner administrative state is enabled
             and the device is operated as the active RPL owner. The value 'inactive'
             is used to indicate that the RPL owner administrative state is enabled,
             but the device is operated as the inactive RPL owner. The value
             'disabled' is used to indicate that the RPL owner administrative
             state of the device is disabled."
        ::= { eltErpsMgmtRAPSVlanEntry 14 }

    eltErpsMgmtRAPSProtectionVlanRangeList1to1024 OBJECT-TYPE
		SYNTAX     OCTET STRING (SIZE (0..128))
		MAX-ACCESS  read-write
		STATUS      deprecated
		DESCRIPTION
			"This object indicates the VLAN range (1-1024)
			 that belongs to the protection VLANs."
		DEFVAL  { "" }
        ::= { eltErpsMgmtRAPSVlanEntry 15 }

    eltErpsMgmtRAPSProtectionVlanRangeList1025to2048 OBJECT-TYPE
		SYNTAX      OCTET STRING (SIZE (0..128))
		MAX-ACCESS  read-write
		STATUS      deprecated
		DESCRIPTION
			"This object indicates the VLAN range (1025-2048)
			 that belongs to the protection VLANs."
		DEFVAL  { "" }
        ::= { eltErpsMgmtRAPSVlanEntry 16 }

    eltErpsMgmtRAPSProtectionVlanRangeList2049to3072 OBJECT-TYPE
		SYNTAX      OCTET STRING (SIZE (0..128))
		MAX-ACCESS  read-write
		STATUS      deprecated
		DESCRIPTION
			"This object indicates the VLAN range (2049-3072)
			 that belongs to the protection VLANs."
		DEFVAL  { "" }
        ::= { eltErpsMgmtRAPSVlanEntry 17 }

    eltErpsMgmtRAPSProtectionVlanRangeList3073to4094 OBJECT-TYPE
		SYNTAX      OCTET STRING (SIZE (0..128))
		MAX-ACCESS  read-write
		STATUS      deprecated
		DESCRIPTION
			"This object indicates the VLAN range (3073-4094)
			 that belongs to the protection VLANs."
		DEFVAL  { "" }
        ::= { eltErpsMgmtRAPSVlanEntry 18 }

    eltErpsMgmtRAPSRevertive OBJECT-TYPE
	    SYNTAX      TruthValue
	    MAX-ACCESS  read-write
	    STATUS      deprecated
	    DESCRIPTION
                "This indicates the revertive mode."
		DEFVAL  { true }
	    ::= { eltErpsMgmtRAPSVlanEntry 19 }

	eltErpsMgmtRAPSProtocolVersion OBJECT-TYPE
        SYNTAX   INTEGER (1|2)
        MAX-ACCESS  read-write
        STATUS      deprecated
        DESCRIPTION
            "This object indicates the ERPS protocol compatibility with other versions of ITU-T G.8032."
		DEFVAL  { 2 }
        ::= { eltErpsMgmtRAPSVlanEntry 20 }

    eltErpsMgmtRAPSPortForcedSwitch OBJECT-TYPE
        SYNTAX      EltErpsMgmtRAPSPortId
        MAX-ACCESS  read-write
        STATUS      deprecated
        DESCRIPTION
            "Forced switch port."
		DEFVAL  { none }
        ::= { eltErpsMgmtRAPSVlanEntry 21 }

    eltErpsMgmtRAPSPortManualSwitch OBJECT-TYPE
        SYNTAX      EltErpsMgmtRAPSPortId
        MAX-ACCESS  read-write
        STATUS      deprecated
        DESCRIPTION
            "Manual switch port."
		DEFVAL  { none }
        ::= { eltErpsMgmtRAPSVlanEntry 22 }

	eltErpsMgmtRAPSRowStatus OBJECT-TYPE
        SYNTAX      RowStatus
        MAX-ACCESS  read-create
        STATUS      deprecated
        DESCRIPTION
            "This object indicates the RowStatus of this entry."
        ::= { eltErpsMgmtRAPSVlanEntry 23 }

-- ----------------------------------------------------------------------------
-- eltErpsMgmtSubRingCtrlTable
-- ----------------------------------------------------------------------------

    eltErpsMgmtSubRingCtrlTable OBJECT-TYPE
        SYNTAX      SEQUENCE OF EltErpsMgmtSubRingCtrlEntry
        MAX-ACCESS  not-accessible
        STATUS      deprecated
        DESCRIPTION
            "This table contains ERPS sub-ring configuration information."
        ::= { eltMesErpsMgmt 2 }

    eltErpsMgmtSubRingCtrlEntry OBJECT-TYPE
        SYNTAX      EltErpsMgmtSubRingCtrlEntry
        MAX-ACCESS  not-accessible
        STATUS      deprecated
        DESCRIPTION
            "A list of ERPS sub-ring configuration information."
        INDEX    {eltErpsMgmtSubRingCtrlRAPSVlanId, eltErpsMgmtSubRingCtrlSubRingRAPSVlanId}
        ::= { eltErpsMgmtSubRingCtrlTable 1 }

    EltErpsMgmtSubRingCtrlEntry ::= SEQUENCE {
            eltErpsMgmtSubRingCtrlRAPSVlanId
                INTEGER,
            eltErpsMgmtSubRingCtrlSubRingRAPSVlanId
            	INTEGER,
            eltErpsMgmtSubRingCtrlTCPropagationState
                EltErpsEnabledState,
            eltErpsMgmtSubRingCtrlRowStatus
            	RowStatus
    }

    eltErpsMgmtSubRingCtrlRAPSVlanId  OBJECT-TYPE
        SYNTAX      INTEGER
        MAX-ACCESS  not-accessible
        STATUS      deprecated
        DESCRIPTION
            "The RAPS VLAN is an index of configuration."
        ::= { eltErpsMgmtSubRingCtrlEntry 1 }

    eltErpsMgmtSubRingCtrlSubRingRAPSVlanId  OBJECT-TYPE
        SYNTAX      INTEGER
        MAX-ACCESS  not-accessible
        STATUS      deprecated
        DESCRIPTION
            "This indicates the ring control VLAN-ID of the sub-ring which connects to another ring."
        ::= { eltErpsMgmtSubRingCtrlEntry 2 }

    eltErpsMgmtSubRingCtrlTCPropagationState  OBJECT-TYPE
        SYNTAX      EltErpsEnabledState
        MAX-ACCESS  read-write
        STATUS      deprecated
        DESCRIPTION
            "This indicates the state of sub-ring topology change propagation."
		DEFVAL  { disabled }
        ::= { eltErpsMgmtSubRingCtrlEntry 3 }

    eltErpsMgmtSubRingCtrlRowStatus OBJECT-TYPE
        SYNTAX      RowStatus
        MAX-ACCESS  read-create
        STATUS      deprecated
        DESCRIPTION
            "This object indicates the RowStatus of this entry."
        ::= { eltErpsMgmtSubRingCtrlEntry 4 }

-- -----------------------------------------------------------------------------
-- eltMesErpsNotify
-- -----------------------------------------------------------------------------

   eltMesErpsNotifyPrefix       OBJECT IDENTIFIER ::= { eltMesErpsNotify 0 }

    eltErpsSFDetectedTrap    NOTIFICATION-TYPE
        OBJECTS     {eltErpsNodeId }
        STATUS      deprecated
        DESCRIPTION
            "When the signal fail occurs, a trap will be generated."
        ::= { eltMesErpsNotifyPrefix 1 }

    eltErpsSFClearedTrap NOTIFICATION-TYPE
        OBJECTS     {eltErpsNodeId }
        STATUS          deprecated
        DESCRIPTION
            "When the signal fail clears, a trap will be generated."
        ::= { eltMesErpsNotifyPrefix 2 }

    eltErpsRPLOwnerConflictTrap   NOTIFICATION-TYPE
        OBJECTS     {eltErpsNodeId }
        STATUS          deprecated
        DESCRIPTION
            "When a conflict occurs, a trap will be generated."
        ::= { eltMesErpsNotifyPrefix 3 }

    eltMesErpsNotificationBindings   OBJECT IDENTIFIER ::= { eltMesErpsNotify 2 }

    eltErpsNodeId OBJECT-TYPE
            SYNTAX      MacAddress
            MAX-ACCESS  accessible-for-notify
            STATUS      deprecated
            DESCRIPTION
                "This used trap object means the node MAC."
            ::= { eltMesErpsNotificationBindings 1 }

END
